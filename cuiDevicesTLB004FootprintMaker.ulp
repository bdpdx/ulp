#usage "CUI Devices TLB004-508 Terminal Block Footprint Maker"

#include "common.ulp"

// all units in this file in mm

string command = "";

real gridMajorDivision = 0.5;
real gridMinorDivision = 0.01;
string gridUnit = "mm";

real distanceBetweenPadCentersHorizontally = 5.08;
real distanceBetweenPadCentersVertically = 7.62;
real padDrillDiameter = 1.4;
real annularRingWidth = max(0.25 * padDrillDiameter, minimumAnnularRingWidth);
real padDiameter = padDrillDiameter + annularRingWidth * 2;

int numberOfPadsHorizontally = 26;
int numberOfPadsVertically = 2;

void createFootprint() {
	selectLayer(LAYER_TOP);
	
	real horizontalDistanceBetweenPadCenters = 5.08;
	real verticalDistanceBetweenPadCenters = 7.62;
	real partHeight = 14.05;
	real partWidth = horizontalDistanceBetweenPadCenters * numberOfPadsHorizontally + 2.5;
	
	real topLeftPadX = -partWidth / 2 + 2.6;
	real topLeftPadY = partHeight / 2 - 1.85;
	real x;
	real y;

	int padNumber = 1;
	
	for (int i = 0; i < numberOfPadsHorizontally; ++i) {
		for (int j = 0; j < numberOfPadsVertically; ++j) {
			selectLayer(LAYER_TOP);
		
			x = topLeftPadX + i * horizontalDistanceBetweenPadCenters;
			y = topLeftPadY - j * verticalDistanceBetweenPadCenters;
			
			sprintf(cmd, "pad 'p$%d' %s", padNumber++, point(x, y));
			addCommand(cmd);
			
			if (!(padNumber & 1)) {
				selectLayer(LAYER_TDOCU);
				y = 7.5;
				addCommand("change align center-left");
				sprintf(cmd, "text 'P$%d' R90 %s", (padNumber + 1) / 2, point(x, y));
				addCommand(cmd);
				y = -7.5;
				addCommand("change align center-right");
				sprintf(cmd, "text 'P$%d' R90 %s", (padNumber + 1) / 2, point(x, y));
				addCommand(cmd);
			}
		}
	}

	selectLayer(LAYER_TPLACE);
	drawRectangle(-partWidth / 2, partHeight / 2, partWidth / 2, -partHeight / 2, minimumLineWidth);
	
	selectLayer(LAYER_TNAMES);
	
	addCommand("change align bottom-left");
	
	x = -partWidth / 2 + 1;
	y = -partHeight / 2 + 1;
	
	sprintf(cmd, "text '>NAME' %s", point(x, y));
	addCommand(cmd);

	selectLayer(LAYER_TVALUES);

	x = partWidth / 2 - 1;

	addCommand("change align bottom-right");
	sprintf(cmd, "text '>VALUE' %s", point(x, y));
	addCommand(cmd);
}

void setup() {
	sprintf(cmd, "grid lines on %s %0.02f 1 alt %0.02f %s", gridUnit, gridMajorDivision, gridMinorDivision, gridUnit);
	addCommand(cmd);

	addCommand("change font vector");
	addCommand("change ratio 8");
	addCommand("change shape round");
	
	change("drill", padDrillDiameter);
	change("size", minimumTextHeight);
	change("width", minimumLineWidth);

	if (padDiameter > 0) {
		change("diameter", padDiameter);
	} else {
		addCommand("change diameter auto");
	}
}

int main() {
	output("/tmp/ulp.log", "wt") {
		setup();
		createFootprint();
		Exit();
	}

	return 0;
}
